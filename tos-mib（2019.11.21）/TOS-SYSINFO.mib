-- **********************************************************************
-- TOS-SYSINFO.mib
--
-- Topsec Enterprise Specific MIB: Structure of Management Information
--
-- Copyright (c) 1998-2008, Beijing Topsec Network Security Technology Co.,Ltd. 
-- All Rights Reserved
--
-- The contents of this document are subject to change without notice.
-- **********************************************************************
--
--  Change History:
--
--	Mar 14,2008 - Edit by tos lk 
--
--  Mar 14,2008 - splited from old mib TOSVI-new.mib
--
-- **********************************************************************
TOS-SYSINFO DEFINITIONS ::= BEGIN

	IMPORTS
	    MODULE-IDENTITY,NOTIFICATION-TYPE,OBJECT-TYPE,                                       
	    Integer32, Opaque,Gauge32,IpAddress   
	    FROM SNMPv2-SMI
	    
	    TEXTUAL-CONVENTION,DisplayString,DateAndTime
			FROM SNMPv2-TC
			
			tosMib
			FROM TOS-SMI;
			
	--system information 
	sysInfo MODULE-IDENTITY
		  LAST-UPDATED "200803170000Z"  
	    ORGANIZATION "TOPSEC"
	    CONTACT-INFO
	            " Topsec Beijing
	              China
	              E-mail: support@topsec.com.cn "
	    
	    DESCRIPTION
	            "the product information table"
	            
	    REVISION     "200509140000Z" 
	    DESCRIPTION
	            "Initial version."
	    
	    REVISION    "200801090000Z"
	    DESCRIPTION
	            "Creat this module,some from sysRunning, some new for tp"
	            	            
	    REVISION    "200803140000Z"
	    DESCRIPTION
	            "split the whole mib file into several part"

	    REVISION    "200803140000Z"
	    DESCRIPTION
	            "edit the file tos-sysinfo.mib"
	
	    REVISION    "200803170000Z"
	    DESCRIPTION
	            "add object sysSnmpVersion"    
	
	    ::= { tosMib 3}
	    
	sysProductSN OBJECT-TYPE
	    SYNTAX      DisplayString 
	    MAX-ACCESS  read-only
	    STATUS      current
	    DESCRIPTION
	            "product serial number,Each device has only one psn"
	    ::= { sysInfo 1 }
	    
	sysProductType OBJECT-TYPE
	    SYNTAX      DisplayString 
	    MAX-ACCESS  read-only
	    STATUS      current
	    DESCRIPTION
	            "product's hardware type "
	    ::= { sysInfo 2 }
	    
	sysSoftwareVersion OBJECT-TYPE
	    SYNTAX      DisplayString 
	    MAX-ACCESS  read-only
	    STATUS      current
	    DESCRIPTION
	            "product's OS type and version"
	    ::= { sysInfo 3 }
	    
	sysHardwareId OBJECT-TYPE
	    SYNTAX      DisplayString 
	    MAX-ACCESS  read-only
	    STATUS      current
	    DESCRIPTION
	            "porduct hardware ID,Each device have one and only ID"
	    ::= { sysInfo 4 }
	    
	sysSnmpVersion OBJECT-TYPE
	    SYNTAX      DisplayString
	    MAX-ACCESS  read-only
	    STATUS      current
	    DESCRIPTION
	            "The SNMP agent version of the system."
	    ::= { sysInfo 5 }
	   
	sysVpnEngine OBJECT-TYPE
	    SYNTAX      DisplayString 
	    MAX-ACCESS  read-only
	    STATUS      current
	    DESCRIPTION
	            "VPN engine version of VPN module"
	    ::= { sysInfo 6 }
	    
	sysAntiVirusEngine OBJECT-TYPE
	    SYNTAX      DisplayString 
	    MAX-ACCESS  read-only
	    STATUS      current
	    DESCRIPTION
	            "Anti-virus engine version of AV module"
	    ::= { sysInfo 7 }
	    	    
	sysAntiVirusLibrary OBJECT-TYPE
	    SYNTAX      DisplayString 
	    MAX-ACCESS  read-only
	    STATUS      current
	    DESCRIPTION
	            "Virus define library version of AV module"
	    ::= { sysInfo 8 }
	    	    
	sysSecurityEngine OBJECT-TYPE
	    SYNTAX      DisplayString 
	    MAX-ACCESS  read-only
	    STATUS      current
	    DESCRIPTION
	            "the security engines of this device,depended on license "
	    ::= { sysInfo 9 }
	    
	sysDpiSupport OBJECT-TYPE
	    SYNTAX      DisplayString 
	    MAX-ACCESS  read-only
	    STATUS      current
	    DESCRIPTION
	            "DPI services of this device, depended on license"
	    ::= { sysInfo 10 }
	    
	sysNatSupport OBJECT-TYPE
	    SYNTAX      DisplayString 
	    MAX-ACCESS  read-only
	    STATUS      current
	    DESCRIPTION
	            "NAT services of this device, depended on license"
	    ::= { sysInfo 11 }
	    
	sysAuthenticationSupport OBJECT-TYPE
	    SYNTAX      DisplayString 
	    MAX-ACCESS  read-only
	    STATUS      current
	    DESCRIPTION
	            "Authentivation protocol of this device, depended on license"
	    ::= { sysInfo 12 }
	    	    
	sysService OBJECT-TYPE
	    SYNTAX      DisplayString 
	    MAX-ACCESS  read-only
	    STATUS      current
	    DESCRIPTION
	            "Services which device can support, depended on license"
	    ::= { sysInfo 13 }
	    
	sysDynamicRoutingProtocol OBJECT-TYPE
	    SYNTAX      DisplayString 
	    MAX-ACCESS  read-only
	    STATUS      current
	    DESCRIPTION
	            "Dynamic routing protocol that device support, depended on license"
	    ::= { sysInfo 14 }
	    
	sysMaxSession OBJECT-TYPE
	    SYNTAX      Integer32
	    MAX-ACCESS  read-only
	    STATUS      current
	    DESCRIPTION
	            "Max session that device support, depended on license"
	    ::= { sysInfo 15 }
	    
	sysMaxVrcClient OBJECT-TYPE
	    SYNTAX      Integer32
	    MAX-ACCESS  read-only
	    STATUS      current
	    DESCRIPTION
	            " Max vrc client that device support, depended on license"
	    ::= { sysInfo 16 }	    
	    
	--end system information 
	
END
