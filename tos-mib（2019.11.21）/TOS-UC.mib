-- **********************************************************************
-- TOS-UC.mib
--
-- Topsec Enterprise Specific MIB: Structure of Management Information
--
-- Copyright (c) 1998-2008, Beijing Topsec Network Security Technology Co.,Ltd. 
-- All Rights Reserved
--
-- The contents of this document are subject to change without notice.
-- **********************************************************************
--
--  Change History:
--
--	Mar 14,2008 - Edit by tos lk 
--
--  Mar 14,2008 - splited from old mib TOSVI-new.mib
--
-- **********************************************************************

TOS-UC DEFINITIONS ::= BEGIN

	IMPORTS
	    MODULE-IDENTITY,NOTIFICATION-TYPE,OBJECT-TYPE,                                       
	    Integer32, Opaque,Gauge32,IpAddress   
	    FROM SNMPv2-SMI
	    
	    TEXTUAL-CONVENTION,DisplayString,DateAndTime
			FROM SNMPv2-TC
			
			tosMib
			FROM TOS-SMI;
			
	--start list TOS User table information
	tosUserTable OBJECT-TYPE 
	   SYNTAX      SEQUENCE OF TosUserEntry	
	   MAX-ACCESS  not-accessible
	   STATUS      current		  
	    DESCRIPTION
	            "split the whole mib file into several part"
		::= {  tosMib 18 }

	tosUserEntry OBJECT-TYPE
		SYNTAX     TosUserEntry
		MAX-ACCESS not-accessible
		STATUS     current
		DESCRIPTION
		        "An entry (conceptual row) containing the information on current vpn users."
		INDEX      {  userIndex }
		::= { tosUserTable 1 }

	TosUserEntry ::= SEQUENCE {
		userIndex               INTEGER,
		userName                DisplayString,
		userLoginIp             IpAddress,
		userLoginTime           DisplayString
	    }

	userIndex OBJECT-TYPE
		SYNTAX      INTEGER 
		MAX-ACCESS  read-only
		STATUS      current
		DESCRIPTION
		        "Index of User Table ."
		::= { tosUserEntry 1 }

	userName OBJECT-TYPE
		SYNTAX	DisplayString
		MAX-ACCESS	read-only
		STATUS	current
		DESCRIPTION  
		"Name of  User Table ."
		::= { tosUserEntry 2  } 

	userLoginIp OBJECT-TYPE
		SYNTAX     IpAddress
		MAX-ACCESS read-only
		STATUS     current
		DESCRIPTION
		        "The IP where User login."
		::= { tosUserEntry 3 }

	userLoginTime OBJECT-TYPE
		SYNTAX	DisplayString
		MAX-ACCESS	read-only
		STATUS	current
		DESCRIPTION  
		"The Time when User login ."
		::= { tosUserEntry 4 } 
	--end list TOS User table information
	
	--start list TOS Configure table information
	tosConfigTable   OBJECT-TYPE
		SYNTAX      SEQUENCE OF  TosConfigEntry	
		MAX-ACCESS  not-accessible
		STATUS      current		  
		DESCRIPTION
	        "split the whole mib file into several part"

		::= { tosMib 19  }

	tosConfigEntry OBJECT-TYPE
		SYNTAX     TosConfigEntry
		MAX-ACCESS not-accessible
		STATUS     current
		DESCRIPTION
		        "An entry (conceptual row) containing the information of configure information."
		INDEX      {  configIndex }
		::= {  tosConfigTable 1 }

	TosConfigEntry ::= SEQUENCE {
		configIndex              INTEGER,
		configContent            DisplayString
	     }

	configIndex OBJECT-TYPE
		SYNTAX      INTEGER
		MAX-ACCESS  read-only
		STATUS      current
		DESCRIPTION
		        "The Index of the Config table ."
		::= { tosConfigEntry 1 }


	configContent  OBJECT-TYPE
		SYNTAX      DisplayString
		MAX-ACCESS  read-only
		STATUS      current
		DESCRIPTION
		        "The detail information of configure."
		::= { tosConfigEntry 2 }
	--end list TOS Configure table information

END
