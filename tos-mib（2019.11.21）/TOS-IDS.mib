-- **********************************************************************
-- TOS-IDS.mib
--
-- Topsec Enterprise Specific MIB: Structure of Management Information
--
-- Copyright (c) 1998-2008, Beijing Topsec Network Security Technology Co.,Ltd. 
-- All Rights Reserved
--
-- The contents of this document are subject to change without notice.
-- **********************************************************************
--
--  Change History:
--
--	Mar 14,2008 - Edit by tos lk 
--
--  Mar 14,2008 - splited from old mib TOSVI-new.mib
--
-- **********************************************************************

TOS-IDS DEFINITIONS ::= BEGIN

	IMPORTS
	    MODULE-IDENTITY,NOTIFICATION-TYPE,OBJECT-TYPE,                                       
	    Integer32, Opaque,Gauge32,IpAddress   
	    FROM SNMPv2-SMI
	    
	    TEXTUAL-CONVENTION,DisplayString,DateAndTime
			FROM SNMPv2-TC
			
			tosMib
			FROM TOS-SMI;
			
	--star list TOS IDS table information 
	
	 tosIDS  MODULE-IDENTITY
		  LAST-UPDATED "200803140000Z"  
	    ORGANIZATION "TOPSEC"
	    CONTACT-INFO
	            " Topsec Beijing
	              China
	              E-mail: support@topsec.com.cn "
		  DESCRIPTION
		          "The (conceptual) table containing information on IDS table."
		        	    
	    REVISION     "200509140000Z" 
	    DESCRIPTION
	            "Initial version."
	            
	    REVISION    "200803140000Z"
	    DESCRIPTION
	            "split the whole mib file into several part"
			::= { tosMib 11 }

	idsTotal OBJECT-TYPE
	    SYNTAX      Counter32
	    MAX-ACCESS  read-only
	    STATUS      current
	    DESCRIPTION
	            "attack totals."
	    ::= { tosIDS 1 }		

  idsIpoption OBJECT-TYPE
      SYNTAX      Counter32
      MAX-ACCESS  read-only
      STATUS      current
      DESCRIPTION 
              "ipoption."
      ::= { tosIDS 2 }

	idsIpprotocol OBJECT-TYPE
	    SYNTAX      Counter32
	    MAX-ACCESS  read-only
	    STATUS      current
	    DESCRIPTION
	            "ipprotocol."
	    ::= { tosIDS 3 }
	    
	idsPort OBJECT-TYPE
	    SYNTAX      Counter32
	    MAX-ACCESS  read-only
	    STATUS      current
	    DESCRIPTION
	            "port."
	    ::= { tosIDS 4 }

	idsTcpscan OBJECT-TYPE
	    SYNTAX      Counter32
	    MAX-ACCESS  read-only
	    STATUS      current
	    DESCRIPTION
	            "tcpscan."
	    ::= { tosIDS 5 }

	idsWinnuke OBJECT-TYPE
	    SYNTAX      Counter32
	    MAX-ACCESS  read-only
	    STATUS      current
	    DESCRIPTION
	            "winnuke."
	    ::= { tosIDS 6 }

	idsIcmpContent OBJECT-TYPE
	    SYNTAX      Counter32
	    MAX-ACCESS  read-only
	    STATUS      current
	    DESCRIPTION
	            "icmp_content."
	    ::= { tosIDS 7 }

	idsSmurf OBJECT-TYPE
	    SYNTAX      Counter32
	    MAX-ACCESS  read-only
	    STATUS      current
	    DESCRIPTION
	            "smurf."
	    ::= { tosIDS 8 }

	idsLand OBJECT-TYPE
	    SYNTAX      Counter32
	    MAX-ACCESS  read-only
	    STATUS      current
	    DESCRIPTION
	            "land ."
	    ::= { tosIDS 9 }
	
	idsPingofdeath OBJECT-TYPE
	    SYNTAX      Counter32
	    MAX-ACCESS  read-only
	    STATUS      current
	    DESCRIPTION
	            "pingofdeath."
	    ::= { tosIDS 10 }

	idsTeardrop OBJECT-TYPE
	    SYNTAX      Counter32
	    MAX-ACCESS  read-only
	    STATUS      current
	    DESCRIPTION
	            "teardrop ."
	    ::= { tosIDS 11 }


  idsTarga3 OBJECT-TYPE
      SYNTAX      Counter32
      MAX-ACCESS  read-only
      STATUS      current
      DESCRIPTION
              "targa3."
      ::= { tosIDS 12 }

	idsIpspoof  OBJECT-TYPE
	    SYNTAX      Counter32
	    MAX-ACCESS  read-only
	    STATUS      current
	    DESCRIPTION
	            "ipspoof ."
	    ::= { tosIDS 13 }

	idsPortscan OBJECT-TYPE
	    SYNTAX      Counter32
	    MAX-ACCESS  read-only
	    STATUS      current
	    DESCRIPTION
	            "portscan."
	    ::= { tosIDS 14 }

	idsSynflood  OBJECT-TYPE
	    SYNTAX      Counter32
	    MAX-ACCESS  read-only
	    STATUS      current
	    DESCRIPTION
	            "synflood."
	    ::= { tosIDS 15 }

	idsUdpflood OBJECT-TYPE
	    SYNTAX      Counter32
	    MAX-ACCESS  read-only
	    STATUS      current
	    DESCRIPTION
	            "udpflood."
	    ::= { tosIDS 16 }

	idsIcmpflood  OBJECT-TYPE
	    SYNTAX      Counter32
	    MAX-ACCESS  read-only
	    STATUS      current
	    DESCRIPTION
	            "icmpflood ."
	    ::= { tosIDS 17 }

	idsIpsweep  OBJECT-TYPE
	    SYNTAX      Counter32
	    MAX-ACCESS  read-only
	    STATUS      current
	    DESCRIPTION
	            "ipsweep ."
	    ::= { tosIDS 18 }

-- end TOS IDS list information table
	    
END
